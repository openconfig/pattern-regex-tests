module python-plugin-test {
  prefix "ppt";
  namespace "urn:openconfig-regex-plugin-test";

  import pattern-test { prefix "pt"; }

  description
    "contains pyang plugin test cases for pattern statements";

  leaf ipv4 {
    type string {
        pattern 'ip[vV]4';
    }
    // Good test cases.
    pt:pattern-test-pass "ipv4";
    pt:pattern-test-pass "ipV4";
    pt:pattern-test-fail "ipv6";
    // Bad test cases.
    pt:pattern-test-fail "ipv4";
    pt:pattern-test-pass "ipv6";
  }
  leaf ipv4-2 {
    // No test cases.
    type string {
        pattern 'ip[vV]4';
    }
  }
  leaf ipv4-3 {
    // Unrestricted type.
    type string;
  }
  leaf ipv4-4 {
    type union {
        type string {
            pattern 'ip[vV]4';
        }
        // Unrestricted union subtype.
        type string;
    }
    pt:pattern-test-pass "ipv4";
  }
}
