module regexp-test {
  prefix "rt";
  namespace "urn:openconfig-regexp-test";

  import pattern-test { prefix "pt"; }
  import openconfig-bgp-types { prefix "ocbgpt"; }
  import openconfig-inet-types { prefix "ocinet"; }
  import openconfig-packet-match-types { prefix "oc-pkt-match-types"; }
  import openconfig-yang-types { prefix "oc-yang"; }

  leaf hex-string {
    type oc-yang:hex-string;
    pt:pattern-test-pass "00000";
    pt:pattern-test-pass "fffff";
    pt:pattern-test-pass "FFFFF";
    pt:pattern-test-pass "0123456789abcdefABCDEF";
    pt:pattern-test-pass "FEDCBAfedcba9876543210";
    pt:pattern-test-fail "g";
    pt:pattern-test-fail "G";
    pt:pattern-test-fail "0123456789abcdefABCDEFG";
    pt:pattern-test-fail "FEDCBAgfedcba9876543210";
  }
  leaf dotted-quad {
    type oc-yang:dotted-quad;
    pt:pattern-test-pass "0.0.0.0";
    pt:pattern-test-pass "255.255.255.255";
    pt:pattern-test-pass "249.249.249.249";
    pt:pattern-test-pass "8.8.8.8";
    pt:pattern-test-pass "42.42.42.42";
    pt:pattern-test-pass "192.168.10.249";
    pt:pattern-test-fail ".255.255.255.255";
    pt:pattern-test-fail "255.255.255.255.";
    pt:pattern-test-fail "01.0.0.0";
    pt:pattern-test-fail "0.01.0.0";
    pt:pattern-test-fail "0.0.01.0";
    pt:pattern-test-fail "0.0.0.01";
    pt:pattern-test-fail "011.024.0.0";
    pt:pattern-test-fail "256.255.255.255";
    pt:pattern-test-fail "255.256.255.255";
    pt:pattern-test-fail "255.255.256.255";
    pt:pattern-test-fail "255.255.255.256";
    pt:pattern-test-fail "a.8.8.8";
    pt:pattern-test-fail "8.a.8.8";
    pt:pattern-test-fail "8.8.a.8";
    pt:pattern-test-fail "8.8.8.a";
    pt:pattern-test-fail "300.0.0.0";
    pt:pattern-test-fail "0.300.0.0";
    pt:pattern-test-fail "0.0.300.0";
    pt:pattern-test-fail "0.0.0.300";
  }
  leaf date-and-time {
    type oc-yang:date-and-time;
    pt:pattern-test-pass "0000-01-01T00:00:00Z";
    pt:pattern-test-pass "9999-12-31T23:59:59Z";
    pt:pattern-test-pass "1985-04-12T23:20:50.52Z";
    pt:pattern-test-pass "2001-04-12T23:20:50.42424242Z";
    pt:pattern-test-pass "1996-12-19T16:39:57-08:00";
    pt:pattern-test-pass "2006-12-20T00:39:57Z";
    pt:pattern-test-pass "1937-01-01T12:00:27.87+00:20";
    // Out of range tests.
    pt:pattern-test-fail "0000-00-01T00:00:00Z";
    pt:pattern-test-fail "0000-13-01T00:00:00Z";
    pt:pattern-test-fail "0000-20-01T00:00:00Z";
    pt:pattern-test-fail "0000-01-00T00:00:00Z";
    pt:pattern-test-fail "0000-01-32T00:00:00Z";
    pt:pattern-test-fail "0000-01-40T00:00:00Z";
    pt:pattern-test-fail "0000-01-01T24:00:00Z";
    pt:pattern-test-fail "0000-01-01T30:00:00Z";
    pt:pattern-test-fail "0000-01-01T00:60:00Z";
    pt:pattern-test-fail "0000-01-01T00:00:61Z";
    pt:pattern-test-fail "0000-01-01T00:00:70Z";
    // + tests.
    pt:pattern-test-fail "0000-01-01T00:00:00Z+";
    pt:pattern-test-pass "0000-01-01T00:00:00+00:00";
    pt:pattern-test-fail "0000-01-01T00:00:00+24:00";
    pt:pattern-test-fail "0000-01-01T00:00:00+30:00";
    pt:pattern-test-fail "0000-01-01T00:00:00+00:60";
    // - tests.
    pt:pattern-test-fail "0000-01-01T00:00:00Z-";
    pt:pattern-test-pass "0000-01-01T00:00:00-00:00";
    pt:pattern-test-fail "0000-01-01T00:00:00-24:00";
    pt:pattern-test-fail "0000-01-01T00:00:00-30:00";
    pt:pattern-test-fail "0000-01-01T00:00:00-00:60";
    // Leap second tests.
    pt:pattern-test-pass "1990-12-31T23:59:60Z";
    pt:pattern-test-pass "1990-12-31T15:59:60-08:00";
    pt:pattern-test-fail "1990-12-31T15:59:61-08:00";
    pt:pattern-test-fail "1990-12-31T15:59:70-08:00";
  }
  leaf date {
    type oc-yang:date;
    pt:pattern-test-pass "0000-01-01";
    pt:pattern-test-pass "9999-12-31";
    pt:pattern-test-pass "1985-04-12";
    pt:pattern-test-pass "2001-04-12";
    pt:pattern-test-pass "1996-12-19";
    pt:pattern-test-pass "2006-12-20";
    pt:pattern-test-pass "1937-01-01";
    // Out of range tests.
    pt:pattern-test-fail "0000-00-01";
    pt:pattern-test-fail "0000-01-00";
    pt:pattern-test-fail "0000-13-01";
    pt:pattern-test-fail "0000-20-01";
    pt:pattern-test-fail "0000-33-01";
    pt:pattern-test-fail "0000-01-32";
    pt:pattern-test-fail "0000-01-40";
  }
  leaf phys-address {
    type oc-yang:phys-address;
    pt:pattern-test-pass "00:00:00:00:00:00:00:00:00";
    pt:pattern-test-pass "ff:0F:f0:ff:FF:ff:00:ff:ff";
    pt:pattern-test-pass "aA:bB:Cc:Dd:eE:fF:01:23:45:67:89:93";
    pt:pattern-test-fail "FFFFFFFF";
    pt:pattern-test-fail "FF::";
    pt:pattern-test-fail "a:b:c:d:e:0";
  }
  leaf mac-address {
    type oc-yang:mac-address;
    pt:pattern-test-pass "00:00:00:00:00:00";
    pt:pattern-test-pass "ff:0F:f0:ff:FF:ff";
    pt:pattern-test-pass "aA:bB:Cc:Dd:eE:fF";
    pt:pattern-test-pass "01:23:45:67:89:aB";
    pt:pattern-test-fail "FFFFFFFF";
    pt:pattern-test-fail "FF::";
    pt:pattern-test-fail "a:b:c:d:e:0";
  }
  leaf ipv4-address {
    type ocinet:ipv4-address;
    pt:pattern-test-pass "255.255.255.255";
    pt:pattern-test-pass "0.0.0.0";
    pt:pattern-test-pass "1.1.1.1";
    pt:pattern-test-fail "256.255.255.255";
    pt:pattern-test-fail "1.1.1.256";
    pt:pattern-test-fail "256.1.1.1%eth0";
  }
  leaf ipv4-address-zoned {
    type ocinet:ipv4-address-zoned;
    pt:pattern-test-pass "255.1.1.1%eth0";
    pt:pattern-test-pass "255.255.255.255%eth1";
    pt:pattern-test-pass "0.0.0.0%PoRt3";
    pt:pattern-test-pass "1.1.1.1%FOX10_mouse5";
    pt:pattern-test-fail "255.1.1.1%";
    pt:pattern-test-fail "255.255.255.255";
    pt:pattern-test-fail "0.0.0.0";
    pt:pattern-test-fail "1.1.1.1";
    pt:pattern-test-fail "256.255.255.255";
    pt:pattern-test-fail "1.1.1.256";
    pt:pattern-test-fail "256.1.1.1%eth0";
  }
  leaf ip-address {
    type ocinet:ip-address;
    pt:pattern-test-pass "255.255.255.255";
    pt:pattern-test-pass "2001:db8::1";
    pt:pattern-test-fail "invalid-data";
    pt:pattern-test-pass "::1";
  }
  leaf bgp-std-community {
    type ocbgpt:bgp-std-community-type;
    pt:pattern-test-pass "15169:42";
    pt:pattern-test-pass "6643:21438";
    pt:pattern-test-pass "29636:4444";
    pt:pattern-test-pass "65535:65535";
    pt:pattern-test-pass "0:0";
    pt:pattern-test-fail "65536:1";
    pt:pattern-test-fail "1:65536";
    pt:pattern-test-fail "425353:comm";
  }
  leaf bgp-ext-community {
    type ocbgpt:bgp-ext-community-type;
    // Type 1 extended communities (2b AS: 4b integer)
    pt:pattern-test-pass "29636:10";
    pt:pattern-test-pass "5413:4294967295";
    pt:pattern-test-pass "4445:0";
    pt:pattern-test-fail "1273:4294967296";
    pt:pattern-test-pass "2856:400";
    pt:pattern-test-fail "5400:invalid";
    pt:pattern-test-fail "i6643:10";
    pt:pattern-test-pass "15169:22432";
    // Type 2 extended communities: (4b IP: 2b integer)
    pt:pattern-test-fail "1.1.1.1:4294967296";
    pt:pattern-test-fail "1.2.3.4.5:10";
    pt:pattern-test-pass "82.42.12.35:65535";
    pt:pattern-test-fail "82.42.12.35:66536";
    pt:pattern-test-fail "254.254.256.254:10";
    pt:pattern-test-pass "0.0.0.0:200";
    pt:pattern-test-fail "leading192.0.2.1:65535";
    // 4b AS : 2b integer
    pt:pattern-test-fail "4294967296:65535";
    pt:pattern-test-pass "4294967295:65535";
    pt:pattern-test-pass "0:65535";
    pt:pattern-test-pass "4294967295:0";
    pt:pattern-test-fail "4294967296:0";
    // Route Target Type 1 - route-target:<2b AS>:<4b local>
    pt:pattern-test-fail "route-target:64";
    pt:pattern-test-pass "route-target:65535:10";
    pt:pattern-test-fail "route-TARGET:65535:10";
    pt:pattern-test-fail "route-target:15169:4294967296";
    pt:pattern-test-pass "route-target:15169:4294967295";
    // Route Target Type 2 - route-target:<ipv4>:<2b local>
    pt:pattern-test-fail "route-target:256.0.2.36:10";
    pt:pattern-test-pass "route-target:192.0.2.1:10";
    pt:pattern-test-fail "route-target:192.0.2.1:65536";
    // Route Target w/ 4B AS:<2b local>
    pt:pattern-test-pass "route-target:4294967295:10";
    pt:pattern-test-fail "route-target:4294967296:10";
    pt:pattern-test-pass "route-target:5413:65535";
    // Route Origin Type 1 - route-target:<2b AS>:<4b local>
    pt:pattern-test-fail "route-origin:53";
    pt:pattern-test-pass "route-origin:65535:10";
    pt:pattern-test-fail "route-ORIGINTRAIL:65535:10";
    pt:pattern-test-fail "route-origin:15169:4294967296";
    pt:pattern-test-pass "route-origin:15169:4294967295";
    // Route Origin Type 2 - route-target:<ipv4>:<2b local>
    pt:pattern-test-fail "route-origin:512.0.2.36:10";
    pt:pattern-test-pass "route-origin:10.18.253.24:10";
    pt:pattern-test-fail "route-origin:192.168.1.1:65536";
    // Route Origin w/ 4B AS:<2b local>
    pt:pattern-test-pass "route-origin:4294967295:5353";
    pt:pattern-test-fail "route-origin:4294967296:9009";
    pt:pattern-test-pass "route-origin:5413:65535";
  }
  leaf ipv6-address {
    type ocinet:ipv6-address;
    pt:pattern-test-pass "2620::1000:3202:23e:e1ff:fec7:7112";
    pt:pattern-test-pass "fe80::23e:e1ff:fec7:7112";
    pt:pattern-test-fail "fe80::23e:NOTVALID:fec7:7112";
    pt:pattern-test-fail "FFFF::NOTE::FFFF";
    pt:pattern-test-fail "FFFF::1::42";
  }
  leaf ipv4-prefix {
    type ocinet:ipv4-prefix;
    pt:pattern-test-pass "0.0.0.0/0";
    pt:pattern-test-pass "255.255.255.255/32";
    pt:pattern-test-fail "256.0.0.0/31";
    pt:pattern-test-pass "1.2.3.0/24";
    pt:pattern-test-fail "1.2.3.4/33";
  }
  leaf ipv6-prefix {
    type ocinet:ipv6-prefix;
    pt:pattern-test-pass "::/0";
    pt:pattern-test-pass "FFFF:FFFF:FFFF:FFFF:FFFF:FFFF:FFFF:FFFF/128";
    pt:pattern-test-fail "FFFF:FFFF:FFFF:NOTVALID:FFFF:FFFF:FFFF:FFFF/64";
    pt:pattern-test-pass "2001:DB8::/32";
    pt:pattern-test-fail "2001:4C20::/129";
  }
  leaf ip-prefix {
    type ocinet:ip-prefix;
    pt:pattern-test-pass "0.0.0.0/0";
    pt:pattern-test-pass "192.0.2.1/32";
    pt:pattern-test-fail "192.0.2.2/33";
    pt:pattern-test-pass "FE80::CAFE/128";
    pt:pattern-test-fail "FE81::CAFE:DEAD:BEEF/129";
  }
  leaf domain-name {
    type ocinet:domain-name;
    pt:pattern-test-pass "ambroseesorbma";
    pt:pattern-test-fail "ambrose esorbma";
    pt:pattern-test-pass "claire.";
    pt:pattern-test-fail "~~~-+=.";
    pt:pattern-test-fail "ambrose esorbma";
    pt:pattern-test-pass "012345678901234567890123456789012345678901234567890123456789012.";
    pt:pattern-test-fail "0123456789012345678901234567890123456789012345678901234567890123";
  }
  leaf port-num-range {
    type oc-pkt-match-types:port-num-range;
    pt:pattern-test-pass "0..0";
    pt:pattern-test-pass "00000..00000";
    pt:pattern-test-pass "00..00";
    pt:pattern-test-pass "01..01";
    pt:pattern-test-pass "0..65535";
    pt:pattern-test-pass "01111..09999";
    pt:pattern-test-pass "9999..59999";
    pt:pattern-test-pass "60536..60999";
    pt:pattern-test-pass "60999..61999";
    pt:pattern-test-pass "62999..63999";
    pt:pattern-test-pass "64999..65535";
    pt:pattern-test-fail "65535..66646";
    pt:pattern-test-fail "65535..65536";
    pt:pattern-test-fail "65535..65545";
    pt:pattern-test-fail "65535..65635";
    pt:pattern-test-fail "66535..65535";
    pt:pattern-test-fail "66999..67890";
    pt:pattern-test-fail "70000..70000";
  }
}
