module types {
  prefix "t";
  namespace "urn:openconfig-regex-oc-test-types";

  description
    "contains gotest test types for OpenConfig POSIX pattern statements";

  typedef ipv4-string {
    type string {
      pattern 'ip[vV]4';
    }
  }

  typedef ipv6-string {
    type string {
      pattern 'ip[vV]6';
    }
  }

  typedef ip-string {
    type union {
      type string {
        pattern 'ip[vV]4';
      }
      type string {
        pattern 'ip[vV]6';
      }
    }
  }

  typedef ip-string-typedef {
    type union {
      type ipv4-string;
      type ipv6-string;
    }
  }

  typedef ipv4-str {
    type ipv4-string {
      pattern 'ipv4';
    }
  }
}
