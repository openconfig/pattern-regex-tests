module simple-leaf-fail {
  prefix "slf";
  namespace "urn:openconfig-regex-oc-test";

  import pattern-test { prefix "pt"; }
  import openconfig-extensions { prefix "oc-ext"; }

  description
    "contains gotest test cases for OpenConfig POSIX pattern statements";

  leaf ipv-0 {
    type string {
      oc-ext:posix-pattern 'ip[vV]4';
    }
    pt:pattern-test-fail "ipv4";
    pt:pattern-test-pass "ipv6";
  }
}
